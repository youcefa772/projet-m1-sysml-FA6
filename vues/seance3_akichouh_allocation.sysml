package allocationConseil {
    doc /* Séance 3 (AKICHOUH) : allocation des actions de la séance 2 aux composants */
    private import parkingConseil::actions::*;
    private import materielDetectionGuidage::*;

    /* consulterConseilStationnement */
    allocate consulterConseilStationnement.mesurerOccupation to parking.detectionGuidage.capteursPlaces;
    allocate consulterConseilStationnement.prevoirOccupation to parking.serveurCentral.modulePrevision;
    allocate consulterConseilStationnement.basculerModeDegrade to parking.serveurCentral.superviseur;
    allocate consulterConseilStationnement.calculerTempsTotalParZone to parking.serveurCentral.moduleRecommandation;
    allocate consulterConseilStationnement.recommanderZoneEtEntree to parking.serveurCentral.moduleRecommandation;
    allocate consulterConseilStationnement.afficherRecommandation to parking.detectionGuidage.panneauxLumineux;

    /* retrouverVehicule */
    allocate retrouverVehicule.verifierQRCode to parking.serveurCentral.superviseur;
    allocate retrouverVehicule.afficherRefus to parking.detectionGuidage.bornesClient;
    allocate retrouverVehicule.localiserVehicule to parking.detectionGuidage.camerasZone;
    allocate retrouverVehicule.afficherPlaceEtChemin to parking.detectionGuidage.bornesClient;
}
